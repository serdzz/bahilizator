#version 1
// Бахилизатор v2.0 — Генератор схемы STM32F103C8T6 Bluepill
// Запуск из Eagle: RUN bahilizator_schematic.ulp
//
// Создаёт схему с:
// - STM32F103C8T6 (48-pin LQFP)
// - SIM800L GSM модем (USART1)
// - HD44780 дисплей через PCF8574 (I2C1)
// - EEPROM 24C08 (I2C1)
// - NRI G-13.6000 монетоприёмник (6 каналов + BLOCK через NPN)
// - Хопперы A/B (Enable + Sensor)
// - 4 кнопки + 2 двери
// - iButton 1-Wire (PA11)
// - LED красный/зелёный
// - Power Fail детектор

string program_name = "bahilizator_schematic.ulp";
string project_name = "bahilizator";

// Проверяем что активна схема
if (schematic) {
    schematic(S) {
        // Создаём листы схемы
        // Лист 1: MCU + питание
        // Лист 2: GSM модем
        // Лист 3: I2C (дисплей + EEPROM)
        // Лист 4: Монетоприёмник + хопперы
        // Лист 5: Кнопки + двери + прочее
        
        dlgMessageBox("Схема Бахилизатора будет создана.\n\nПин-мап STM32F103C8T6 Bluepill:\n\nI2C1: PB6(SCL), PB7(SDA)\nUSART1: PA9(TX→SIM800L), PA10(RX←SIM800L)\nGSM: PA0(PWRKEY), PA1(STATUS), PA2(DTR)\nCoin: PB8-13(CH1-6), PB14(BLOCK)\nButtons: PA3-6(PREV/NEXT/OK/CANCEL)\nDoors: PA7, PA8\n1-Wire: PA11(iButton)\nLED: PC15(RED), PB0(GREEN)\nPower Fail: PB1\n\nВнимание: Компоненты нужно разместить вручную\nпосле создания нетлистов.", "OK");
    }
} else {
    dlgMessageBox("Откройте схему (Schematic) перед запуском ULP!", "OK");
    exit(0);
}

// Пин-мап для справки (выводится в журнал)
string pinmap = "";
pinmap += "=== Бахилизатор Pin Map ===\n";
pinmap += "STM32F103C8T6 Bluepill\n";
pinmap += "I2C1 SCL    = PB6\n";
pinmap += "I2C1 SDA    = PB7\n";
pinmap += "USART1 TX   = PA9  → SIM800L RXD\n";
pinmap += "USART1 RX   = PA10 ← SIM800L TXD\n";
pinmap += "GSM PWRKEY  = PA0  (NPN BC547)\n";
pinmap += "GSM STATUS  = PA1  (делитель 2.8V→3.3V)\n";
pinmap += "GSM DTR     = PA2\n";
pinmap += "Coin CH1    = PB8  (NPN BC547)\n";
pinmap += "Coin CH2    = PB9  (NPN BC547)\n";
pinmap += "Coin CH3    = PB10 (NPN BC547)\n";
pinmap += "Coin CH4    = PB11 (NPN BC547)\n";
pinmap += "Coin CH5    = PB12 (NPN BC547)\n";
pinmap += "Coin CH6    = PB13 (NPN BC547)\n";
pinmap += "Coin BLOCK  = PB14 (прямое управление)\n";
pinmap += "Button PREV = PA3\n";
pinmap += "Button NEXT = PA4\n";
pinmap += "Button OK   = PA5\n";
pinmap += "Button CANCEL=PA6\n";
pinmap += "Door 1      = PA7\n";
pinmap += "Door 2      = PA8\n";
pinmap += "iButton     = PA11 (1-Wire Open-Drain)\n";
pinmap += "LED RED     = PC15\n";
pinmap += "LED GREEN   = PB0\n";
pinmap += "Power Fail  = PB1\n";

printf(pinmap);
exit(0);
